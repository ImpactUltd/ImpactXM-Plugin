(defun c:PLOT_SET_TRANSPARENCY_ON (/ obj_Layouts itm sub_LayoutTransparency)
  (defun sub_LayoutTransparency (layout OnOff / xType xData)
    (setq xData (vlax-make-safearray vlax-vbVariant '(0 . 1)))
    (setq xType (vlax-make-safearray vlax-vbInteger '(0 . 1)))
    (vlax-safearray-fill xData (list (vlax-make-variant "PLOTTRANSPARENCY")(vlax-make-variant OnOff)))
    (vlax-safearray-fill xType (list 1001 1071))
    (vla-setXdata layout xType xData)
    (entmod (entget (vlax-vla-object->ename layout) '("*")))
  )
  (setq	obj_Layouts (vla-get-layouts (vla-get-activedocument (vlax-get-acad-object))))
  (foreach itm (layoutlist)
    (sub_LayoutTransparency (vla-item obj_Layouts itm) 1)
  )
 (princ)
)
