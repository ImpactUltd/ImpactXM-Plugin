(defun c:SAW_1 ( / sset_a )
  (setq sset_a (ssget))
  (command "-saw" "s" "3" sset_a "")
)
(defun c:SAW_2 ( / sset_a )
  (setq sset_a (ssget))
  (command "-saw" "s" "4" sset_a "")
)
(defun c:SAW_3 ( / sset_a )
  (setq sset_a (ssget))
  (command "-saw" "s" "3" sset_a "")
)
(defun c:SAW_4 ( / sset_a )
  (setq sset_a (ssget))
  (command "-saw" "s" "4" sset_a "")
)
(defun c:SAW_? ( / file_path )
  ;(setq file_path (f:getBlockPath "Manuals\\PDF" "IXM_DETAILING_AVC-PRO-SETTINGS.pdf"))
  ;(command "browser" (strcat "file:\/\/\/" file_path))
  (f:help-ixm-plugin-id "22")
)
