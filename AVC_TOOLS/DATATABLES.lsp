(progn ;data tables
  (defun c:IXM_DATTAB_ST_1 (/ sset_a) 
    (setq sset_a (ssget))
    (command "DATATABLE" "s" "1" sset_a "")
  )
  (defun c:IXM_DATTAB_ST_2 (/ sset_a) 
    (setq sset_a (ssget))
    (command "DATATABLE" "s" "2" sset_a "")
  )
  (defun c:IXM_DATTAB_ST_3 (/ sset_a) 
    (setq sset_a (ssget))
    (command "DATATABLE" "s" "3" sset_a "")
  )
  (defun c:IXM_DATTAB_ST_4 (/ sset_a) 
    (setq sset_a (ssget))
    (command "DATATABLE" "s" "4" sset_a "")
  )
  (defun c:IXM_DATTAB_ST_5 (/ sset_a) 
    (setq sset_a (ssget))
    (command "DATATABLE" "s" "5" sset_a "")
  )
)


; (defun c:IXM_DATTAB_ST_? (/ file_path) 
;   (f:help-ixm-plugin-id "22")
; )
