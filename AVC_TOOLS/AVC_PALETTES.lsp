(defun c:AVC_PALETTES_ALL nil
  (vl-cmdf "NAMEPALETTE")
  (vl-cmdf "KINDPALETTE")
  (vl-cmdf "INFOPALETTE")
  (vl-cmdf "USERPALETTE")
)

(defun c:AVC_PALETTES_NKI nil
  (vl-cmdf "NAMEPALETTE")
  (vl-cmdf "KINDPALETTE")
  (vl-cmdf "INFOPALETTE")
)
