(defun subGetPartSize (ss / minpt maxpt boundbox attPt)
  (defun sub:TMatrixFromTo (from to)
    (append
      (mapcar
        (function
    (lambda	(v o)
      (append (trans v from to T) (list o))
    )
        )
        (list '(1. 0. 0.) '(0. 1. 0.) '(0. 0. 1.))
        (trans '(0. 0. 0.) to from)
      )
      (list '(0. 0. 0. 1.))
    )
  )
  
  (defun sub:UcsBoundingBox (obj _OutputMinPtSym _OutputMaxPtSym)
    (and (= (type obj) 'ENAME)
         (setq obj (vlax-ename->vla-object obj))
    )
    (vla-TransformBy obj (vlax-tmatrix (sub:TMatrixFromTo 1 0)))
    (vla-GetBoundingBox obj _OutputMinPtSym _OutputMaxPtSym)
    (vla-TransformBy obj (vlax-tmatrix (sub:TMatrixFromTo 0 1)))
    (set _OutputMinPtSym (vlax-safearray->list (eval _OutputMinPtSym)))
    (set _OutputMaxPtSym (vlax-safearray->list (eval _OutputMaxPtSym)))
  )

  (defun sub:SelSetUcsBBox (aSSet _OutputMinPtSym _OutputMaxPtSym / n l1 l2 ss )

    (setq ss (vlaSSet->eSSet aSSet))
    (repeat (setq n (sslength ss))
      (sub:UcsBoundingBox (ssname ss (setq n (1- n))) _OutputMinPtSym _OutputMaxPtSym)
      (setq l1 (cons (eval _OutputMinPtSym) l1)
            l2 (cons (eval _OutputMaxPtSym) l2)
      )
    )
    (set _OutputMinPtSym (apply 'mapcar (cons 'min l1)))
    (set _OutputMaxPtSym (apply 'mapcar (cons 'max l2)))
  )

  (sub:SelSetUcsBBox ss 'minpt 'maxpt)
  (setq boundbox (mapcar '- maxpt minpt))
  (setq boundbox (sort-list boundbox))
  (setq attPt (trans minpt 1 0))
  (SetWorldUCS)
  (strcat       (rtos   (car boundbox) 5 4) (chr 34) 
          " x " (rtos  (cadr boundbox) 5 4) (chr 34)
          " x " (rtos (caddr boundbox) 5 4) (chr 34)
  )
  ;(princ (strcat "Block's\tt =\t" (rtos (car boundbox)) "\n\tw =\t" (rtos (cadr boundbox)) "\n\tl =\t" (rtos (caddr boundbox))))
  ;(princ)
)

;; (defun c:UCS_bounding_Box_Limits ()
;;   (setq sSet (ssget))
;;   (UCSboundingBoxLimits sSet)
;; )
