(defun UpdatePartData (blockObject blockName partTableName partDesc partSize partNote / aDoc constantAttributeList)
  (setq aDoc (vla-get-activedocument (vlax-get-acad-object)))
  ;(setq catt (variant-value (vla-getConstantAttributes blockObject)))
  (setq constantAttributeList (vlax-invoke blockObject 'GetConstantAttributes))
        ;blockName     (vla-get-effectivename blockObject)
  (vla-put-textstring (nth 0 constantAttributeList) partTableName)
  (vla-put-textstring (nth 1 constantAttributeList) partDesc)
  (vla-put-textstring (nth 2 constantAttributeList) partSize)
  (vla-put-textstring (nth 3 constantAttributeList) partNote)
  ;(if (not eq blockName (vla-get-EffectiveName (vlax-ename->vla-object blockObject)))
  (if (not (eq blockName (vla-get-EffectiveName blockObject)))
    (RenameBlock blockObject blockName)
  )
  (vla-update blockObject)
  0
)
