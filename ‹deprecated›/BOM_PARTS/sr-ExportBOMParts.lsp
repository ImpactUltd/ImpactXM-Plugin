(defun sub:ExportBOMParts (  / listToExport actvDoc *error* varFILEDIA isModelSpace allSelectedSS
                              ent ents objBlock nameBlock attribs destFolderPath)
  (gc)
  (defun *error* ( msg )
    (if (not (member msg '("Function cancelled" "quit / exit abort")))
      (princ (strcat "\nError: " msg))
    )
    (setvar "FILEDIA" varFILEDIA)
    (princ)
  )
  (setq varFILEDIA    (getvar "FILEDIA")
        actvDoc       (vla-get-activeDocument (vlax-get-acad-object))
        isModelSpace  (= acModelSpace (vla-get-activeSpace actvDoc))
  )
  (setvar "FILEDIA" 0)
  (if isModelSpace
    (setq allSelectedSS (ssget '((410 . "Model")(0 . "INSERT"))))
    (progn
      (vla-put-ActiveSpace actvDoc acModelSpace)
      (setq allSelectedSS (ssget '((410 . "Model")(0 . "INSERT"))))
    )
  )
  (setq ents (SelectionSet->entList allSelectedSS))
  (foreach ent ents
    (setq objBlock  (vlax-ename->vla-object ent)
          nameBlock (CL:GetEffectiveBlockName objBlock)
    )
    (if (setq attribs (CL:GetConstantAttributeList objBlock))
        (if (eq (vla-get-tagstring (car attribs)) "TABL")
            (setq listToExport (consU nameBlock listToExport))
        )
    )
  )
  (setq destFolderPath (dcl-SelectFolder "Exported BOM Parts - Select Destination Folder\n\n****  WARNING: Existing BOM Parts will be overwritten  ****" (getRecord "@BOM_LAST_USED" "LAST FOLDER") 64))
  (if destFolderPath
      (progn
        (princ "\n  Exporting:")
        (foreach nameBlock listToExport
          (princ (strcat "\n    " (pad-str nameBlock "" " " 14) " to " (strcat destFolderPath "\\" nameBlock)))
          (command-s "-WBLOCK" (strcat destFolderPath "\\" nameBlock) "=")
          (addRecord "@BOM_LAST_USED" "LAST FOLDER" destFolderPath) 
        )
      )
  )
  (setvar "FILEDIA" varFILEDIA)
  (princ)
)
