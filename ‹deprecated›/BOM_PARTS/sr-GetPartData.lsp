(defun GetPartData (blockObject / list_constAttr obj_constAttr list_Attr obj_Attr partName partTableName partDesc partSize partNote)
  ;(princ "\nsetq")
  (setq sarray_constAttr (vlax-variant-value (vla-GetConstantAttributes blockObject))
        sarray_Attr      (vlax-variant-value (vla-GetAttributes blockObject))
        partName         (vla-get-EffectiveName blockObject)
        list_constAttr   (vlax-safearray->list sarray_constAttr)
        list_Attr        (vlax-safearray->list sarray_Attr)
  )
  
  ;(princ "\nlist_constAttr: ") (prin1 list_constAttr)
  
  ;(princ "\nforeach")
  (foreach obj_constAttr list_constAttr
    ;(princ "\nobj_constAttr: ") (prin1 obj_constAttr)
    (cond
      ((= (vla-get-TagString obj_constAttr) "TABL")
        (setq partTableName (vla-get-TextString obj_constAttr))
      ) 
      ((= (vla-get-TagString obj_constAttr) "DESC")
        (setq partDesc (vla-get-TextString obj_constAttr))
      ) 
      ((= (vla-get-TagString obj_constAttr) "SIZE")
        (setq partSize (vla-get-TextString  obj_constAttr))
      ) 
      ((= (vla-get-TagString obj_constAttr) "NOTE")
        (setq partNote (vla-get-TextString obj_constAttr))
      ) 
    )
  )

  (foreach obj_Attr list_Attr
    (if (= (vla-get-TagString obj_Attr) "PIECE_MARK")
      (setq partPieceMark (vla-get-TextString obj_Attr))
    )
  )
  (prin1 partPieceMark)
  (list partName partTableName partDesc partSize partNote partPieceMark)
)
