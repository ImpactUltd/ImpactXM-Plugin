(defun CopyPartBlock ( blockObject blockName partTableName partDesc partSize partNote / *error* abc app dbc dbx def doc dxf  old prp cpy tmp vrs )

  (defun *error* ( msg )
    (if (and (= 'vla-object (type dbx)) (not (vlax-object-released-p dbx)))
      (vlax-release-object dbx)
    )
    (if (not (wcmatch (strcase msg t) "*break,*cancel*,*exit*"))
      (princ (strcat "\nError: " msg))
    )
    (princ)
  )
  (setq cpy nil)
  ;(if (= 'ename (type blockObject))
    (progn
      (setq app (vlax-get-acad-object)
            doc (vla-get-activedocument app)
            old (vlax-get-property blockObject (if (vlax-property-available-p blockObject 'effectivename) 'effectivename 'name))
            tmp 0
      )
      ;;(while (tblsearch "block" (setq def (strcat (vl-string-left-trim "*" old) "_" (itoa (setq tmp (1+ tmp)))))))
      ;;(while
      ;;  (and (/= "" (setq blockName (getstring t (strcat "\nSpecify blockName block name <" def ">: "))))
      ;;    (or (not (snvalid blockName))
      ;;        (tblsearch "block" blockName)
      ;;    )
      ;;  )
      ;;  (princ "\nBlock name invalid or already exists.")
      ;;)
      ;;(if (= "" blockName)
      ;;  (setq blockName def)
      ;;)
      (setq dbx
        (vl-catch-all-apply 'vla-getinterfaceobject
          (list app
            (if (< (setq vrs (atoi (getvar 'acadver))) 16)
              "objectdbx.axdbdocument"
              (strcat "objectdbx.axdbdocument." (itoa vrs))
            )
          )
        )
      )
      (if (or (null dbx) (vl-catch-all-error-p dbx))
        (princ "\nUnable to interface with ObjectDBX.")
        (progn
          (setq abc (vla-get-blocks doc)
                dbc (vla-get-blocks dbx)
          )
          (vlax-invoke doc 'copyobjects (list (vla-item abc old)) dbc)
          (if (wcmatch old "`**")
            (vla-put-name (vla-item dbc (1- (vla-get-count dbc))) blockName)
            (vla-put-name (vla-item dbc old) blockName)
          )
          (vlax-invoke dbx 'copyobjects (list (vla-item dbc blockName)) abc)
          (vlax-release-object dbx)
          ;(if cpy (setq blockObject (vla-copy blockObject)))
          (if
            (and
              (vlax-property-available-p blockObject 'isdynamicblock)
              (= :vlax-true (vla-get-isdynamicblock blockObject))
            )
            (progn
              (setq prp (mapcar 'vla-get-value (vlax-invoke blockObject 'getdynamicblockproperties)))
              (vla-put-name blockObject blockName)
              (mapcar
                 '(lambda ( a b )
                  (if (/= "ORIGIN" (strcase (vla-get-propertyname a)))
                    (vla-put-value a b)
                  )
                )
                (vlax-invoke blockObject 'getdynamicblockproperties) prp
              )
            )
            (vla-put-name blockObject blockName)
          )
          (if (= :vlax-true (vla-get-isxref (setq def (vla-item (vla-get-blocks doc) blockName))))
            (vla-reload def)
          )
          ;(if cpy (sssetfirst nil (ssadd (vlax-vla-object->ename blockObject))))
        )
      )
    )
  ;)
  (UpdatePartData blockObject blockName partTableName partDesc partSize partNote)
)
