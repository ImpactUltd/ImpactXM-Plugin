(defun c:BOM_PRINT_DICTIONARIES ( / listBOMdicts dictBOM item)
  (sub:ListBOMparts)
  (setq listBOMdicts (listDictionaries))
  (foreach dictBOM listBOMdicts
    (if (= (vl-string-search "@" dictBOM) 0)
        (progn
          (princ (strcat "\n " dictBOM))
          (princ (pad-str "\n " "" "~" (+ (strlen dictBOM) 2)))
          (foreach key (getKeys dictBOM)
              (if (listp (getRecord dictBOM key))
                  (progn
                    (princ (strcat "\n   " key))
                    (foreach item (getRecord dictBOM key)
                      (if (listp item)
                          (progn
                            (princ "\n     ")
                            (princ (strcat  (pad-str (nth 4 item) " " " " 5)
                                            (pad-str (nth 0 item) " " " " 20) 
                                            (pad-str (nth 1 item) " " " " 40) 
                                            (pad-str (nth 2 item) " " " " 40) 
                                            (pad-str (nth 3 item) " " " " 40)) 
                            )
                          )
                          (princ (strcat "\n     " item))
                      )
                    )
                  )
                  (princ (strcat "\n   " key " : " (getRecord dictBOM key)))
              )
              (princ "\n")
          )
          (princ "\n")
        )
    )
  )
  (princ)
)

(defun c:BOM_PRINT_PARTS ( / listBOMdicts dictBOM item)
  (sub:ListBOMparts)
  (setq listBOMdicts (listDictionaries))
  (textpage)
  (foreach dictBOM listBOMdicts
    (if (= dictBOM "@BOM_PARTS_IN_DWG")
        (progn
          (foreach key (getKeys dictBOM)
              (princ (strcat "\n " key))
              (if (listp (getRecord dictBOM key))
                  (foreach item (reverse (getRecord dictBOM key))
                      (if (listp item)
                          (progn
                            (princ "\n    ")
                            (princ (strcat  (pad-str (nth 4 item) " " " " 5)
                                            (pad-str (nth 0 item) " " " " 20)
                                            (pad-str (nth 1 item) " " " " 40)
                                            (pad-str (nth 2 item) " " " " 40)
                                            (pad-str (nth 3 item) " " " " 40))
                            )
                          )
                          (princ (strcat "\n      " item))
                      )
                  )
                  (princ)
              )
              (princ "\n  ")
          )
        )
    )
  )
  (princ)
)
