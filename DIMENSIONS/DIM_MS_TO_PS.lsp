(defun c:DIM_MS_TO_PS ( / pt)
  (command "._MSPACE")
  (setq pt_m_1        (getpoint)
        pt_m_2        (getpoint pt_m_1)
        dist          (distance pt_m_1 pt_m_2)
        str_fraction  (rtos dist 5 5)
        pt_p_1        (trans (trans pt_m_1 1 2) 2 3)
        pt_p_2        (trans (trans pt_m_2 1 2) 2 3)
  )
  (print str_fraction)
  (cond
    ((= str_fraction "0")
        (setq str_fraction "0")
    )
    ((> (vl-string-search " " str_fraction) 0)
        (setq str_fraction (vl-string-subst "\\S" " " str_fraction)
              str_fraction (strcat str_fraction ";" (chr 34))
        )
    )
    ((= (vl-string-search "/" str_fraction) nil)
        (setq str_fraction (strcat str_fraction (chr 34))
        )
    )
    (T
        (setq str_fraction (strcat "\\S" str_fraction ";" (chr 34)))
    )
  )
  (command "._PSPACE")
  (command "dimaligned" "non" pt_p_1 "non" pt_p_2 "TEXT" str_fraction)
)
