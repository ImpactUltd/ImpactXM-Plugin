;|
  Removes the nth item from list
  @Param n Index of item to remove
  @Param l List from which to remove item
  @Returns List without the nth item
|;
(defun f:removeNth ( n l )
    (if (and l (< 0 n))
        (cons (car l) (f:removeNth (1- n) (cdr l)))
        (cdr l)
    )
)

;|
  Compares two file timestamps generated by vl-file-systime
  @Param a 1st timestamp list from vl-file-systime
  @Param b 2nd timestamp list from vl-file-systime
  @Returns 1 if a > b, 0 of a == b, or -1 if a < b
|;
(defun f:filetime-compare ( a b /  )

  ;; remove day of the week (3rd item) from both a & b lists
  (setq a (f:removeNth 2 a)
        b (f:removeNth 2 b)
  )
  
  (cond 
    ((not a) 0)
    ((eq (car a) (car b)) (f:filetime-compare (cdr a) (cdr b)))
    ((> (car a) (car b)) 1)
    (t -1)
  ) 
)

;|
  Search for the lasted modified drawing for block
  CAD user must have a block drawing path in their support path
  @Param fldr sub-folder with blocks path
  @Param blck block file
  @Returns full file path of the most recent block drawing (dwg)
|;
(defun f:getBlockPath ( fldr blck / list_path_prefix path_prefix path_plugin list_path_block bx timeStamp0 timeStamp1)
    
  (setq list_path_prefix (string->list (getvar 'ACADPREFIX) ";"))
  
  (foreach path_prefix list_path_prefix
    (setq path_prefix (strcase path_prefix)
          file_block  (strcat "\\" fldr "\\" blck)
          path_block  (car (vl-directory-files path_prefix file_block ))
    )
    (if path_block
      (setq path_block (strcat path_prefix file_block )
            list_path_block (cons path_block list_path_block)
      )
    )
  )
  ;(princ (strcat "\nFound " (itoa (length list_path_block)) " versions of " blck ". \n\nSearching for most recent version. . . \n"))
  ;(princ (strcat "\nUsing " (car list_path_block) "\n\n"))
  (while (> (length list_path_block) 1)
    (setq timeStamp0 (vl-file-systime (car  list_path_block))
          timeStamp1 (vl-file-systime (cadr list_path_block))
    )
    (setq bx (f:filetime-compare timeStamp0 timeStamp1))
    (cond 
      ((= bx 1)  ; a > b
       (setq list_path_block (f:removeNth 1 list_path_block))
      )
      ((= bx 0)  ; a == b
       (setq list_path_block (f:removeNth 1 list_path_block))
      )
      ((= bx -1) ; a < b
       (setq list_path_block (f:removeNth 0 list_path_block))
      )
    )
  )

  (car list_path_block)
)

;|
  Provides full path and name of the latest template DWT.
  Typically, the DWT have a date stamp at the end of the name to denote version.
  @Param name_dwt type of template ("E30000000-IMPERIAL TEMPLATE" or "E30000000-METRIC TEMPLATE")
  @Returns Full path and correct filename for DWT file.
|;
(defun f:GetDWTname ( name_dwt / *error*)
  (defun *error* (s)
    (princ s)
    (vla-EndUndoMark (actvDoc))
    (princ)
  )
  (setq 
    name_dwt (strcat name_dwt "*.dwt")
    file_name (car (vl-directory-files (vl-filename-directory (f:getBlockPath "Template" name_dwt) ) name_dwt ))
  )
  file_name
)


;|
  Returns a list of all sub-directies (recursively, as in a full sub-directory tree) of a given directory
  @Param path Path of starting directory (ex: "C:\\Users\\Chris Lipinski\\Dropbox (Personal)\\Library\\")
  @Returns List of strings (all sub-directories)
|;
(defun f:get-subdirs (path)
  (apply (quote append)
    (cons (list path)
      (mapcar '(lambda (x) (f:get-subdirs (strcat path x "\\")))
        (cddr (vl-directory-files path nil -1))
      )
    )
  )
)
;(f:get-subdirs "C:\\Users\\Chris Lipinski\\Dropbox (Personal)\\Library\\") <- Massive results!!!


;| 

(f:getBlockPath "Template" (f:GetDWTname "E30000000-IMPERIAL TEMPLATE"))

(f:getBlockPath "Template" (f:GetDWTname "E30000000-METRIC TEMPLATE"))


(princ (f:filetime-compare '(2022 6 4 9 21 19 8 0) '(2022 1 1 9 20 41 14 0)))


(princ (f:getBlockPath "Blocks\\@@COMBINED Blocks" "@COMBINED-CALLOUT-01.dwg"))

(princ (f:getBlockPath "Manuals\\PDF" "IXM_DETAILING_AVC-PRO-SETTINGS.pdf"))

;; C:\Users\Chris Lipinski\Dropbox (Personal)\Library\Manuals\PDF\IXM_DETAILING_AVC-PRO-SETTINGS.pdf

(princ (f:getBlockPath "Template" "E30000000-IMPERIAL TEMPLATE*.dwt"))

(vl-directory-files (f:getBlockPath "Template" "@COMBINED-CALLOUT-01.dwg"))

 |;
;(vl-file-systime filename)

;(vl-directory-files [directory pattern directories])

;C:\Users\customer\Dropbox (Personal)\Library\Blocks\@@COMBINED Blocks\@COMBINED-TITLE BLOCK-02.dwg

;("C:\\USERS\\CUSTOMER\\DROPBOX (PERSONAL)\\LIBRARY-TMP\\BLOCKS\\@@COMBINED Blocks\\@COMBINED-TITLE BLOCK-02.dwg" "C:\\USERS\\CUSTOMER\\DROPBOX (PERSONAL)\\LIBRARY\\BLOCKS\\@@COMBINED Blocks\\@COMBINED-TITLE BLOCK-02.dwg")

;ACADPREFIX = "
;C:\Users\chris\AppData\Roaming\Autodesk\AutoCAD 2020\R23.1\enu\support;
;C:\Program Files\Autodesk\AutoCAD 2020\support;
;C:\Program Files\Autodesk\AutoCAD 2020\support\en-US
;C:\Program Files\Autodesk\AutoCAD 2020\fonts;
;C:\Program Files\Autodesk\AutoCAD 2020\Express;
;C:\Program Files\Autodesk\AutoCAD 2020\support\color
;C:\Users\chris\AppData\Roaming\Autodesk\ApplicationPlugins\AVC_Pro.bundle\Contents;
;C:\Users\chris\AppData\Roaming\Autodesk\ApplicationPlugins\AVC_Pro.bundle\Contents\Windows
;C:\Users\chris\AppData\Roaming\Autodesk\ApplicationPlugins\Impact XM Plug-Ins.bundle\Contents;
;C:\Users\chris\AppData\Roaming\Autodesk\ApplicationPlugins\LipinskiCAD.bundle\Contents
;C:\Users\chris\AppData\Roaming\Autodesk\ApplicationPlugins\Gile_Increment.bundle\Contents;
;C:\Users\chris\AppData\Roaming\Autodesk\ApplicationPlugins\Gile_OsnapPalette.bundle\Contents
;C:\Users\chris\AppData\Roaming\Autodesk\ApplicationPlugins\Gile_OsnapPalette.bundle\Contents\OsnapPalette;
;C:\Program Files\Autodesk\AutoCAD 2020\drv;" (read only)
