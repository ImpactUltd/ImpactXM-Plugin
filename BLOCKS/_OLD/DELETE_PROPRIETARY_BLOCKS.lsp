(defun c:DELETE_PROPRIETARY_BLOCKS (/ *error*
                                    obj_BlockRef list_objBlockRefs list_COMB_BlockRefs )
  (vl-load-com)
  (defun *error* (msg)
    (vla-EndUndoMark (actvDoc))
    (if (not (wcmatch (strcase msg t) "*break,*cancel*,*exit*"))
      (princ (strcat "\nError: " msg))
      (princ (strcat "\n" msg " by User"))
    )
  )
  (vla-StartUndoMark (actvDoc))
    
  (setq list_objBlockRefs (SelectionSet->objList (ssget "_X" '((0 . "INSERT")))))
  (foreach obj_BlockRef list_objBlockRefs
    ;(print (vla-get-EffectiveName obj_BlockRef))
    (if (wcmatch (vla-get-EffectiveName obj_BlockRef) "`@COMBINED*")
      (setq list_COMB_BlockRefs (cons obj_BlockRef list_COMB_BlockRefs))
    )
  )
  (foreach obj_BlockRef list_COMB_BlockRefs
    (princ "\nDeleting ")
    (princ (vla-get-EffectiveName obj_BlockRef))
    (vla-Delete obj_BlockRef)
  )
  (c:PURGE_ALL)  
  (vla-EndUndoMark (actvDoc))
  (princ)
)
