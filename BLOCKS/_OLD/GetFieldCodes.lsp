(defun f:fieldCode ( ent / replacefield replaceobject fieldstring enx )
  (defun replacefield ( str enx / ent fld pos )
    (if (setq pos (vl-string-search "\\_FldIdx" (setq str (replaceobject str enx))))
      (progn
        (setq ent (assoc 360 enx)
              fld (entget (cdr ent))
        )
        (strcat
          (substr str 1 pos)
          (replacefield (fieldstring fld) fld)
          (replacefield (substr str (1+ (vl-string-search ">%" str pos))) (cdr (member ent enx)))
        )
      )
      str
    )
  )
  (defun replaceobject ( str enx / ent pos )
    (if (setq pos (vl-string-search "ObjIdx" str))
      (strcat
        (substr str 1 (+ pos 5)) " "
        (f:ObjectID (vlax-ename->vla-object (cdr (setq ent (assoc 331 enx)))))
        (replaceobject (substr str (1+ (vl-string-search ">%" str pos))) (cdr (member ent enx)))
      )
      str
    )
  )
  (defun fieldstring ( enx / itm )
    (if (setq itm (assoc 3 enx))
      (strcat ;|(cdr itm)|; (fieldstring (cdr (member itm enx))))
      (cond ((cdr (assoc 2 enx))) (""))
    )
  )
  (if (and (wcmatch  (cdr (assoc 0 (setq enx (entget ent)))) "TEXT,MTEXT,ATTRIB,MULTILEADER,*DIMENSION")
       (setq enx (cdr (assoc 360 enx)))
       (setq enx (dictsearch enx "ACAD_FIELD"))
       (setq enx (dictsearch (cdr (assoc -1 enx)) "TEXT"))
    )
    (replacefield (fieldstring enx) enx)
  )
)
(defun f:ObjectID ( obj )
  (eval
    (list 'defun 'f:ObjectID '( obj )
      (if
        (and
          (vl-string-search "64" (getenv "PROCESSOR_ARCHITECTURE"))
          (vlax-method-applicable-p (vla-get-Utility (actvDoc)) 'getobjectidstring)
        )
        (list 'vla-getobjectidstring (vla-get-Utility (actvDoc)) 'obj ':vlax-false)
         '(itoa (vla-get-ObjectID obj))
      )
    )
  )
  (f:ObjectID obj)
)
(defun f:fieldCodeX (obj)
  (f:fieldCode (vlax-vla-object->ename obj))
)
